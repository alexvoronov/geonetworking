ICLCM DEFINITIONS AUTOMATIC TAGS ::= 

BEGIN
-- The root data frame for iGAME Cooperative Lane Change Message
IGAMECooperativeLaneChangeMessage ::= SEQUENCE {
	itsHeader ItsPduHeader,
	iclcm IGAMECooperativeLaneChange-MessageBody
}

ItsPduHeader ::= SEQUENCE {
	protocolVersion ProtocolVersion,
	messageID MessageID,
	stationID StationID
}

IGAMECooperativeLaneChange-MessageBody ::= SEQUENCE {
	generationDeltaTime GenerationDeltaTime,
	iclcmParameters IclcmParameters
}

IclcmParameters ::= SEQUENCE {
	vehicleContainerHighFrequency VehicleContainerHighFrequency,
	vehicleContainerLowFrequency VehicleContainerLowFrequency OPTIONAL,
	mostImportantObjectContainer MostImportantObjectContainer,
	laneObject LaneObject,
	pairIdObject PairIdObject,
	mergeObject MergeObject,
	scenarioObject ScenarioObject
}

VehicleContainerHighFrequency ::= SEQUENCE {
	vehicleRearAxleLocation VehicleRearAxleLocation,
	controllerType ControllerType,
	vehicleResponseTime VehicleResponseTime,
	targetLongitudinalAcceleration TargetLongitudinalAcceleration,
	timeHeadway TimeHeadway,
	cruiseSpeed CruiseSpeed
}

VehicleContainerLowFrequency ::= SEQUENCE {
	participantsReady ParticipantsReady OPTIONAL,
	startPlatoon StartPlatoon OPTIONAL,
	endOfScenario EndOfScenario OPTIONAL
}

MostImportantObjectContainer ::= SEQUENCE {
	mioID StationID,
	mioRange MioRange,
	mioBearing MioBearing,
	mioRangeRate MioRangeRate
}

LaneObject ::= SEQUENCE {
	lane Lane
}

PairIdObject ::= SEQUENCE {
	forwardID StationID,
	backwardID StationID,
	acknowledgeFlag AcknowledgeFlag
}

MergeObject ::= SEQUENCE {
	mergeRequest MergeRequest,
	mergeSafeToMerge MergeSafeToMerge,
	mergeFlag MergeFlag,
	mergeFlagTail MergeFlagTail,
	mergeFlagHead MergeFlagHead
}

ScenarioObject ::= SEQUENCE {
	platoonID PlatoonID,
	distanceTravelledCZ DistanceTravelledCZ,
	intention Intention,
	counterIntersection CounterIntersection
}

VehicleResponseTime ::= SEQUENCE {
	vehicleResponseTimeConstant VehicleResponseTimeConstant,
	vehicleResponseTimeDelay VehicleResponseTimeDelay
}

--
-- ASN1-CAM,DENM shared header declaration
--
ProtocolVersion ::= INTEGER { currentVersion(1) } (0..255)
MessageID ::= INTEGER { denm(1), cam(2), iclcm(10) } (0..255)
StationID ::= INTEGER(0..4294967295)

GenerationDeltaTime ::= INTEGER { oneSecond(1000) } (0..65535)
VehicleRearAxleLocation ::= INTEGER { oneMeter(100) } (0..4095)
ControllerType ::= INTEGER { manual(0), cc(1), acc(2), cacc(3) } (0..3)
TargetLongitudinalAcceleration ::= INTEGER { oneMeterPerSecondSquared(100), unavailable(1001) } (-1000..1001)
TimeHeadway ::= INTEGER { oneSecond(10), unavailable(361) } (0..361)
CruiseSpeed ::= INTEGER { oneMeterPerSecond(100), unavailable(5001) } (0..5001)
ParticipantsReady ::= INTEGER { notReady(0), ready(1) } (0..1)
StartPlatoon ::= INTEGER { startPlatoonAAtSpeed80kph(0), startPlatoonBAt60kph(1) } (0..1)
EndOfScenario ::= INTEGER { endOfScenario(1) } (1..1)
MioRange ::= INTEGER { oneMeter(100), unavailable(65535) } (0..65535)
MioBearing ::= INTEGER { zeroRadians(0), oneRadianRight(500), unavailable(1572) } (-1571..1572)
MioRangeRate ::= INTEGER { zeroMeterPerSecond(0), oneMeterPerSecond(100), unavailable(32767) } (-32767..32767)
Lane ::= INTEGER { laneOne(1), laneTwo(2), laneThree(3), unavailable(4) } (1..4)
AcknowledgeFlag ::= INTEGER { notAcknowledged(0), acknowledged(1) } (0..1)
MergeRequest ::= INTEGER { noMergeRequest(0), mergeRequest(1) } (0..1)
MergeSafeToMerge ::= INTEGER { notSafe(0), safe(1) } (0..1)
MergeFlag ::= INTEGER { notMergeReady(0), mergeReady(1) } (0..1)
MergeFlagTail ::= INTEGER { notLastVehicle(0), lastVehicle(1) } (0..1)
MergeFlagHead ::= INTEGER { notFirstVehicle(0), firstVehicle(1) } (0..1)
PlatoonID ::= INTEGER { platoonA(1), platoonB(2), notUsed(3) } (0..255)
DistanceTravelledCZ ::= INTEGER { oneMeter(10) } (0..10000)
Intention ::= INTEGER { straightNoTurning(1), turnLeft(2), turnRight(3) } (1..3)
CounterIntersection ::= INTEGER { noVehicles(0), oneVehicle(1) } (0..3)
VehicleResponseTimeConstant ::= INTEGER { oneSecond(100), unavailable(1001) } (0..1001)
VehicleResponseTimeDelay ::= INTEGER { oneSecond(100), unavailable(1001) } (0..1001)

END
